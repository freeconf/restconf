module fc-stocklib {
	namespace "org.freeconf/stock";
	prefix "stock";
    description "management of various objects on C2 library";
	revision 0000-00-00;

    typedef clientAuthType {
        type enumeration {
            enum NoClientCert {
                value 0;
            }
            enum RequestClientCert {
                value 1;
            }
            enum RequireAnyClientCert {
                value 2;
            }
            enum VerifyClientCertIfGiven {
                value 3;
            }
            enum RequireAndVerifyClientCert {
                value 4;
            }
        }
    }
    
    grouping tls {

        leaf clientAuth {
            description "Client Cert Authentication";
            type clientAuthType;
        }
        leaf serverName {
            description "Name identified in certificate for this server";
            type string;
        }

        container cert {
            leaf certFile {
                description "PEM encoded certification";
                type string;
            }
            leaf keyFile {
                description "PEM encoded private key used to build certificate";
                type string;
            }
        }

        container ca {
            leaf certFile {
                description "PEM encoded certificate of certificate authority used to sign certificate";
                type string;
            }
        }
    }
}
