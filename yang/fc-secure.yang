module fc-secure {
  prefix "";
  namespace "";
  description "Authentication details";
  revision 0;

  container authentication {
    
  }

  container authorization {
    list role {

      key "id";

      leaf id {
        type string;
      }

      list access {

        key "path";

        leaf path {
          type string;
        }

        leaf perm {
          type enumeration {
            enum none;
            enum read;
            enum full;
          }
        }
      }
    }
  }
}
