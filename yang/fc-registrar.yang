module fc-registrar {

    revision 0;
    
    rpc register {
        input {
            leaf deviceId {
                description "Id that is unique to this device in the infrastructure pool";
                type string;
                mandatory true;
            }
            leaf address {
                description  "Optional.  Will use incoming address of request.  Hint: If you use the text
                  phrase '{REG_ADD}' anywhere in the address, it will be replaced by the IP address found
                  in the registration request. This does not include the port number because often that
                  is not typically the port used when registering.  Example  https://{REG_ADDR}:8090/restconf";

                type string;
                mandatory true;
            }
        }
    }    

    grouping deviceHnd {
        leaf deviceId {
            type string;
        }

        leaf address {
            type string;
        }        
    }

    list registration {
        key "deviceId";
        config false;
        uses deviceHnd;
    }

    notification update {
        uses deviceHnd;
    }
}
